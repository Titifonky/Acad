(defun modif_bloc (plan / chemin nom_bloc pt_insert_bloc)
  (setq	chemin	       "HYPERSTEELPAGEHEADER=C:\\Documents and Settings\\Etienne\\Mes documents\\Dessins\\Cartouche\\xxxxxxxx\\HYPERSTEELPAGEHEADER.dwg"
	nom_bloc       (ssname (ssget "_X"
				      '((-4 . "<AND")
					(0 . "INSERT")
					(2 . "HYPERSTEELPAGEHEADER")
					(-4 . "AND>")
				       )
			       )
			       0
		       )
	pt_insert_bloc (cdr (assoc '10 (entget nom_bloc)))
  )
  (setvar "ATTREQ" 0)
  (setvar "CMDECHO" 0)
  (entdel nom_bloc)
  (command "_purge" "_all" "*" "_n")
  (setq chemin (vl-string-subst plan "xxxxxxxx" chemin))
  (command "-inserer" chemin pt_insert_bloc 1 1 0)
)

(defun lst_cmd (plan / nom_proto)
  (vl-load-com)
  (command "_zoom" "_all")
  (setq nom_proto (strcase (getvar "DWGNAME")))
  (and (= plan "Tout")
       (cond ((vl-string-search "ASSEMBLAGE" nom_proto)
	      (setq plan "Assemblage")
	     )
	     ((vl-string-search "DEBIT" nom_proto)
	      (setq plan "Debit")
	     )
	     ((vl-string-search "ENSEMBLE" nom_proto)
	      (setq plan "Ensemble")
	     )
       )
  )
  (and (vl-string-search (strcase plan) nom_proto)
       (modif_bloc plan)
  )
  (princ)
)

(lst_cmd "Ensemble")
