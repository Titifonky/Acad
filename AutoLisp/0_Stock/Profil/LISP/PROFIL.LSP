;Programme Lisp AFPA TSECM LOMME
;Modifié le 27.02.06
;Objet : Générateur de profil

;***********************initialise erreur
(defun err_fer (s) 
                 
 (if (/= s "Function cancelled")
   (princ (strcat "\nErreur survenue dans le programme Générateur de profil : " s "\n"))
  )
  (setvar "osmode" ini_obj)
  (setvar "cmdecho" 1)             
  (setq *error* olderr)
  (princ)
)
(DEFUN attente ()
	(alert "FONCTION NON DISPONIBLE VOIR L.B")
)
;*********************initialise programme
(setq fer "IPE")
(setq type_fer "?") 



	;********************* à modifier en fonction du dossier racine ********************* 

(setq racine_dossier "C:/Documents and Settings/etienne c/Mes documents/Acad - Bibliothèque/Bibliothèque Lisp/1 - Autoload/Profil")

	;************************************************************************************ 


(setq chemin (strcat racine_dossier "/donnees/ipe.dat"))
(setq lon 4)
(setq image_fer "ip")
;******************DEBUT PROGRAMME*******

(defun c:fer (/ ini_obj ini_ortho)
 (setq olderr *error* 
        *error* err_fer)
	(setq rotation "0") 
	(setq bloc_action 0) 
	(setq valeur 1)
	(setq hh nil)
	(setq v_fer " ")
	(setq defi " ")
	(setq selec_imag 1)

	(setq olderr *error*
	*error* aa_err )
	(setvar "cmdecho" 0)
	(setq ini_obj (getvar "osmode"))
	(setq ini_ortho (getvar "orthomode"))
	(setvar "orthomode" 0)

	(setq sc_dcl_id (load_dialog (strcat racine_dossier "/dcl/gene_pro.dcl")))
	(if (< sc_dcl_id 0) (exit))
  (if (not (new_dialog "profil" sc_dcl_id)) (exit))
	(set_tile "edit_col" fer)
	(set_tile "nomdubloc" "aucun")
	(boucle)

;;;;;;;;;;;;;;; Definition de l'action bouton

  (action_tile "list_col" "(choix_liste $value)")
  (action_tile "edit_col" "(cedit_act $value)")
  (action_tile "icon1" "(selec_ipe)")
  (action_tile "icon2" "(selec_ipn $value)")
  (action_tile "icon3" "(selec_hea $value)")
  (action_tile "icon4" "(selec_heb $value)")
  (action_tile "icon5" "(selec_UPN $value)")
  (action_tile "icon6" "(selec_UAP $value)")
  (action_tile "icon7" "(selec_COR $value)")
  (action_tile "icon8" "(selec_CORL $value)")
  (action_tile "icon9" "(selec_UPE $value)")

;***********ANGLE DE ROTATION**********
	(set_tile ;|MSG0|;"rot1" ;|MSG0|;"1")
	(setq rot1 1)
	(action_tile ;|MSG0|;"rot1" ;|MSG0|;"(selec_1)")
	(action_tile ;|MSG0|;"rot2" ;|MSG0|;"(selec_2)")
	(action_tile ;|MSG0|;"rot3" ;|MSG0|;"(selec_3)")
	(action_tile ;|MSG0|;"rot4" ;|MSG0|;"(selec_4)")
	(action_tile ;|MSG0|;"rot5" ;|MSG0|;"(selec_5)")
	(action_tile ;|MSG0|;"rot6" ;|MSG0|;"(selec_6)")
	(action_tile ;|MSG0|;"rot7" ;|MSG0|;"(selec_7)")

;*******SELECTION D'ACROCHAGE
(action_tile "m_imag" "(point_inser)")
;*******BLOC
(action_tile ;|MSG0|;"cbloc" ;|MSG0|;"(cbloc)")
(action_tile "nombloc" "(def_bloc)")
;********FINAL*********
(setq fin fer)
(if (= valeur "0") ((setq fer 0)))
(action_tile "cancel" "(setq fer 0)")
(action_tile "help" "(attente)")
(action_tile "info" "(info)")
(start_dialog)
(unload_dialog sc_dcl_id)
(if (= fer "IPE") (ipe))
(if (= fer "HEA") (hea))
(if (= fer "HEB") (heb))
(if (= fer "IPN") (ipn))
(if (= fer "UAP") (uap))
(if (= fer "UPN") (upn))
(if (= fer "COR") (cor))
(if (= fer "CORL") (corl))
(if (= fer "UPE") (upe))
(if (= fer 0) (princ))

(setq valeur value)
(setq fer fin)
(setq *error* olderr)      
(princ)
)

;**********selection******************
(defun choix_liste (value)
(setq valeur value)
(setq val value)
(set_tile ;|MSG0|;"valeur_fer" ;|MSG0|;v_fer)
	(setq valselc 0)
	(setq rech_fer list_fer) 
	(while (/= (atoi valeur) valselc)
	(setq rech_fer (cdr rech_fer))
	(setq valselc (+ valselc 1))
	)
	(setq c (car rech_fer))
(setq type_fer (substr c 1 lon))
(setq type_fer (itoa (atoi type_fer)))
(if (= fer "COR")
	(progn
	(setq ep_fer (itoa (atoi (substr c 4 2))))
	(setq type_fer (strcat type_fer "_ep" ep_fer))
	)
)
(set_tile "type_fer" ;|MSG0|;type_fer )
(set_tile "nomdubloc" ;|MSG0|; "aucun")
(setq bloc_action 0)
(set_tile ;|MSG0|;"cbloc" ;|MSG0|;"0")
)
;*******DEFINITION DE L'EMPLACEMENT DES BASES DE DONNEES**********
(defun selec_ipe ()
	(setq fer "IPE")
(set_tile "edit_col" fer)
(setq chemin (strcat racine_dossier "/donnees/IPE.dat"))
(setq defi "nom   b    a      e    r    h1")
(setq lon 4)
(setq type_fer "?")
(setq image_fer "ip")
(boucle)
)

(defun selec_ipn (value)
	(setq fer "IPN")
	(set_tile "edit_col" fer)
(setq chemin (strcat racine_dossier "/donnees/IPN.dat"))
(setq defi "nom   b     a     e      r     r1    h1" )
(setq lon 4)
(setq type_fer "?")
(setq image_fer "ip")
(boucle)
)

(defun selec_hea (value)
	(setq fer "HEA")
(set_tile "edit_col" fer)
(setq chemin (strcat racine_dossier "/donnees/HEA.dat"))
(setq defi "nom     h    b     a     e     r    h1" )
(setq lon 4)
(setq type_fer "?")
(setq image_fer "h")
(boucle)
)

(defun selec_heb (value)
	(setq fer "HEB")
(set_tile "edit_col" fer)
(setq chemin (strcat racine_dossier "/donnees/HEB.dat"))
(setq defi "nom     h     b     a      e    r    h1" )
(setq lon 4)
(setq type_fer "?")
(setq image_fer "h")
(boucle)
)

(defun selec_uap (value)
	(setq fer "UAP")
(set_tile "edit_col" fer)
(setq chemin (strcat racine_dossier "/donnees/UAP.dat"))
(setq defi "nom   b    a     e      h1" )
(setq lon 4)
(setq type_fer "?")
(setq image_fer "u")
(boucle)
)

(defun selec_upe (value)
	(setq fer "UPE")
(set_tile "edit_col" fer)
(setq chemin (strcat racine_dossier "/donnees/UPE.dat"))
(setq defi "nom   b    a     e      h1" )
(setq lon 4)
(setq type_fer "?")
(setq image_fer "u")
(boucle)
)

(defun selec_upn (value)
	(setq fer "UPN")
(set_tile "edit_col" fer)
(setq chemin (strcat racine_dossier "/donnees/UPN.dat"))
(setq defi "nom    b    a     e      r     r1   h1" )
(setq lon 4)
(setq type_fer "?")
(setq image_fer "u")
(boucle)
)

(defun selec_cor (value)
	(setq fer "COR")
(set_tile "edit_col" fer)
(setq chemin (strcat racine_dossier "/donnees/cor_egal.dat"))
(setq defi "Cot  ep  r" )
(setq lon 3)
(setq image_fer "c")
(setq type_fer "?")
(boucle)
)
(defun selec_corl (value)
	(setq fer "CORL")
(set_tile "edit_col" fer)
(setq chemin (strcat racine_dossier "/donnees/cor_l.dat"))
(setq defi "Cot  ep  r" )
(setq lon 3)
(setq image_fer "c")
(setq type_fer "?")
(boucle)
)
;******Chargement base de donnees**********
(defun boucle ()
(set_tile ;|MSG0|;"fer" ;|MSG0|;fer )
(set_tile ;|MSG0|;"definition" ;|MSG0|;defi)
(set_tile ;|MSG0|;"valeur_fer" ;|MSG0|;defi)
(setq f (open chemin "r"))
(setq nbr 5)
(setq l (read-line f))
(setq l (read-line f))
(setq l (read-line f))
(setq l (read-line f))
(setq l (read-line f))
(setq list_fer '())
   (setq nm 0)
	(while (/= "fin" nm)
	(setq nbr (+ nbr 1))
	(setq init_nul (- nbr 5))
	(setq list_fer (cons l list_fer))
	(setq l (read-line f))
	(setq nnn (length list_fer))
	(if (not l) (setq nm "fin"))
	)

  (start_list "list_col")
  (mapcar 'add_list list_fer)
  (end_list)
(close f)
(setq fin fer)
(setq filtre (strcat fer "*"))
(set_tile "type_fer" type_fer)
(setq nom_bl nil)
	(menu_image)
)
;;;;;;;;;;;;;;;;;;;;;;;;;;;;;;;;;;;;;;;;;;;;;;;;;;;;;;;;;;;;;;;;;;;

;*************PARAMETRAGE

(defun der (g)
	(* pi (/ g 180.0))
)

;                       *****************************************
;                       *       GENERATEUR DE CORNIERES         *
;                       *****************************************
(defun cor ()
(setq a (atoi (substr c 1 3)))
(setq b a)
(setq ee (atoi (substr c 4 2)))
(setq r (atoi (substr c 7 2)))
(setq d1 (atof (substr c 10 4)))
(setq d2 d1)
(cor_generateur)
)

(defun corl ()
(setq a (atoi (substr c 1 3)))
(setq b (atoi (substr c 5 3)))
(setq ee (atof (substr c 9 4)))
(setq r (atof (substr c 14 2)))
(setq d2 (atof (substr c 17 4)))
(setq d1 (atof (substr c 22 4)))
(cor_generateur)
)

(defun cor_generateur ()

;*******Attribution des donnees
(setq r1 (/ r 2.0))
(setq pc (getpoint "Point d'insertion :"))
(setvar "osmode" 0)
(setq pt_i pc)
(setq pt_cen (polar (polar pc (der 270) d2) (der 180) d1))
(setq pt_bg (setq pt_i pc))
(setq pt_bc (polar pc (der 180) (/ b 2.0)))
(setq pt_bd (polar pc (der 180) b))
(setq pt_cc (polar pc (der 180) a))
(setq pt_hg (polar pt_bc (der 270) a))
(setq pt_hc (polar pc (der 270) a))
(setq pt_hd (polar pc (der 270) (/ a 2.0)))
(rech_pti)
;*******Definition des points****************
(setq pt1 (polar pc (der 90) a))
(setq pt2 (polar pt1 (der 0) (- ee r1)))
(setq pt3 (polar pt2 (der 0) r1))
(setq pt3 (polar pt3 (der 270) r1))
(setq pt4 (polar pt3 (der 270) (- a (+ ee r1 r))))
(setq pt5 (polar pt4 (der 0) r))
(setq pt5 (polar pt5 (der 270) r))
(setq pt6 (polar pt5 (der 0) (- b (+ ee  r r1))))
(setq pt7 (polar pt6 (der 0) r1))
(setq pt7 (polar pt7 (der 270) r1))
(setq pt8 (polar pt7 (der 270) (- ee r1)))

;******TRACAGE DU CONTOUR********************
(setvar "osmode" 0)
(command "_.pline" pc "_w" 0 "" "_w" 0 "" pt1 pt2 "a" "a" "-90" "r" r1 pt3
 "li" pt4 "a" "r" r pt5 "li" pt6 "a" "a" "-90" "r" r1 pt7 "li" pt8 "c")
(rot)
)
;**********************************************************************
;                       *******************************************
;                       *SOUS PROGRAMME DE IPE HEA HEB *
;                       *******************************************
(defun gip ()
(setq olderr *error*
	*error* g_profil_err )

(setq pc (getpoint "Point d'insertion :"))
(setvar "osmode" 0)
(setq pt_i pc)
(setq pt_cen (setq pt_i pc))
(setq pt_bg (polar (polar pc (der 0) (/ b 2.0)) (der 90) (/ h 2.0)))
(setq pt_bc (polar pc (der 90) (/ h 2.0)))
(setq pt_bd (polar (polar pc (der 180) (/ b 2.0)) (der 90) (/ h 2.0)))
(setq pt_cc (polar pc (der 0) (/ b 2.0)))
(setq pt_hg (polar pt_bg (der 270) h))
(setq pt_hc (polar pt_bc (der 270) h))
(setq pt_hd (polar pt_bd (der 270) h))
(rech_pti)
(setq pt1 (polar pc (der 180) (/ a 2.0)))
(setq pt1 (polar pt1 (der 90) (- (/ h 2.0) (+ e r))))
(setq pt2 (polar pt1 (der 90) r))
(setq pt2 (polar pt2 (der 180) r))
(setq pt3 (polar pt2 (der 180) (- b1 ee)))
(setq pt4 (polar pt3 (der 90) e))
(setq pt5 (polar pt4 (der 0) b))
(setq pt6 (polar pt5 (der 270) e))
(setq pt7 (polar pt6 (der 180) (- b1 ee)))
(setq pt8 (polar pt7 (der 270) r))
(setq pt8 (polar pt8 (der 180) r))
(setq pt9 (polar pt8 (der 270) (- h (+ r r e e))))
(setq pt10 (polar pt9 (der 270) r))
(setq pt10 (polar pt10 (der 0) r))
(setq pt11 (polar pt10 (der 0) (- b1 ee)))
(setq pt12 (polar pt11 (der 270) e))
(setq pt13 (polar pt12 (der 180) b))
(setq pt14 (polar pt13 (der 90) e))
(setq pt15 (polar pt14 (der 0) (- b1 ee)))
(setq pt16 (polar pt15 (der 90) r))
(setq pt16 (polar pt16 (der 0) r))
;
(setvar "osmode" 0)
(command "_.pline" pt1 "_w" 0 "" "A" "R" r pt2 "li" pt3 pt4 pt5 pt6 pt7
"A" "R" r pt8 "li" pt9 "A" "R" r pt10 "li" pt11
 pt12 pt13 pt14 pt15 "A" "R" r pt16 "li" "c")
;
(rot)
(setvar "cmdecho" 1)
(setq *error* olderr)
(princ)
)

;**********************************************************************

;                       *****************************************
;                       *       GENERATEUR DE IPE               *
;                       *****************************************
(defun ipe (/ plan)
(setq h (atoi (substr c 1 3)))
(setq b (atof (substr c 5 3)))
(setq a (atof (substr c 9 4)))
(setq e (atof (substr c 14 4)))
(setq r (atof (substr c 19 2)))
(setq h1 (atoi (substr c 22 3)))
(setq b1 (/ b 2.0))
(setq a1 (/ a 2.0))
(setq ee (+ a1 r))
(GIP)
)
;**********************************************************************


;                       *****************************************
;                       *       GENERATEUR DE HEA               *
;                       *****************************************
(defun HEA (/ plan)
(setq hh (atoi (substr c 1 4)))
(setq h (atoi (substr c 6 3)))
(setq b (atof (substr c 10 3)))
(setq a (atof (substr c 14 4)))
(setq e (atof (substr c 19 4)))
(setq r (atof (substr c 24 2)))
(setq h1 (atoi (substr c 27 3)))
(setq b1 (/ b 2.0))
(setq a1 (/ a 2.0))
(setq ee (+ a1 r))
(GIP)
)
;**********************************************************************


;                       *****************************************
;                       *       GENERATEUR DE HEB               *
;                       *****************************************
(defun HEB (/ plan)
(setq h (atoi (substr c 6 4)))
(setq b (atof (substr c 11 3)))
(setq a (atof (substr c 15 4)))
(setq e (atof (substr c 20 4)))
(setq r (atof (substr c 25 2)))
(setq h1 (atoi (substr c 28 3)))
(setq b1 (/ b 2.0))
(setq a1 (/ a 2.0))
(setq ee (+ a1 r))
(GIP)
)
;**********************************************************************

;                       *****************************************
;                       *       GENERATEUR DE IPN               *
;                       *****************************************
(defun ipn (/ plan alpha beta aa b2 UX UY 1X x2 y2 2X xu yu 2Y
		 1Y x3 y3 3X xv yv 3Y 4X 4Y)

;****EXTRAIRE LES DIMENSIONS DE LA BASE DE DONNEE**
(setq h (atoi (substr c 1 3)))
(setq b (atof (substr c 5 3)))
(setq a (atof (substr c 9 4)))
(setq e (atof (substr c 14 4)))
(setq r (atof (substr c 20 4)))
(setq r1 (atof (substr c 25 4)))
(setq h1 (atoi (substr c 29 3)))
;**** EQUATION************************************
(setq b2 (/ b 2.0))
(setq alpha (atan 0.14))
(setq beta (atan 7.142857143))
(setq aa (* beta (/ 180.0 pi) -1))
;(setq aa (- 0 aa))
(setq UX (/ b2 2))
(setq UY (- (/ h 2.0) e))
(setq 1X (/ a 2))
(setq x2 (* r (cos beta)))
(setq y2 (* r (sin beta)))
(setq 2X (- (+ 1X r) x2))
(setq xu (- UX 2X))
(setq yu (* xu 0.14))
(setq 2Y (- UY yu))
(setq 1Y (- 2Y y2))
(setq x3 (- r1 (* r1 (cos beta))))
(setq y3 (* r1 (sin beta)))
(setq 3X (- b2 x3))
(setq xv (- 3X UX))
(setq yv (* xv 0.14))
(setq 3Y (+ UY yv))
(setq 4X b2)
(setq 4Y (+ 3Y y3))

;************* CONTOUR
(setq pc (getpoint "Point d'insertion :"))
(setvar "osmode" 0)


(setq pt_i pc)
(setq pt_cen (setq pt_i pc))
(setq pt_bg (polar (polar pc (der 0) (/ b 2.0)) (der 90) (/ h 2.0)))
(setq pt_bc (polar pc (der 90) (/ h 2)))
(setq pt_bd (polar (polar pc (der 180) (/ b 2.0)) (der 90) (/ h 2.0)))
(setq pt_cc (polar pc (der 0) (/ b 2.0)))
(setq pt_hg (polar pt_bg (der 270) h))
(setq pt_hc (polar pt_bc (der 270) h))
(setq pt_hd (polar pt_bd (der 270) h))
(rech_pti)


(setq pt1 (polar pc (der 180) (/ a 2.0)))
(setq pt1 (polar pt1 (der 90) 1Y))
(setq pt2 (polar pc (der 90) 2Y))
(setq pt2 (polar pt2 (der 180) 2X))
(setq pt3 (polar pc (der 90) 3Y))
(setq pt3 (polar pt3 (der 180) 3X))
(setq pt4 (polar pc (der 90) 4Y))
(setq pt4 (polar pt4 (der 180) 4X))
(setq or1 (polar pt3 (der 180) r1))
(setq ptu (polar pc (der 180) UX))
(setq ptu (polar ptu (der 90) UY))
(setq pt5 (polar pc (der 90) (/ h 2.0)))
(setq pt5 (polar pt5 (der 180) b2))
(setq pt6 (polar pt5 (der 0) b))
(setq pt7 (polar pt4 (der 0) b))
(setq or2 (polar pt7 (der 270) r1))
(setq pt8 (polar pc (der 90) 3Y))
(setq pt8 (polar pt8 (der 0) 3X))
(setq pt9 (polar pc (der 90) 2Y))
(setq pt9 (polar pt9 (der 0) 2X))
(setq pt10 (polar pc (der 0) (/ a 2.0)))
(setq pt10 (polar pt10 (der 90) 1Y))
(setq pt11 (polar pc (der 0) (/ a 2.0)))
(setq pt11 (polar pt11 (der 270) 1Y))
(setq pt12 (polar pc (der 270) 2Y))
(setq pt12 (polar pt12 (der 0) 2X))
(setq pt13 (polar pc (der 270) 3Y))
(setq pt13 (polar pt13 (der 0) 3X))
(setq pt14 (polar pc (der 270) 4Y))
(setq pt14 (polar pt14 (der 0) 4X))
(setq or3 (polar pt13 (der 0) r1))
(setq pt15 (polar pt6 (der 270) h))
(setq pt16 (polar pt15 (der 180) b))
(setq pt17 (polar pc (der 270) 4Y))
(setq pt17 (polar pt17 (der 180) 4X))
(setq or4 (polar pt17 (der 90) r1))
(setq pt18 (polar pc (der 270) 3Y))
(setq pt18 (polar pt18 (der 180) 3X))
(setq pt19 (polar pc (der 270) 2Y))
(setq pt19 (polar pt19 (der 180) 2X))
(setq pt20 (polar pc (der 180) (/ a 2.0)))
(setq pt20 (polar pt20 (der 270) 1Y))


;*******-TRACER******
(setvar "osmode" 0)
(command "_.pline" pt1 "_w" 0 "" "A" "R" r pt2 "LI" pt3 "A" 
"DI" or1 pt4 "LI" pt4 pt5 pt6 pt7 "A" "DI" or2 
PT8 "LI" pt9 "A" "R" r pt10 "LI" pt11 "A" "R" r 
pt12 "LI" pt13 "A" "DI" or3 pt14 "LI" pt15
 pt16 pt17 "A" "DI" or4 pt18 "LI" pt19 
"A" "R" r pt20 "LI" "c")
(rot)
)

;*****************************************************************************

;                       *****************************************
;                       *       GENERATEUR DE UAP               *
;                       *****************************************
(defun UAP (/ plan)
(setq h (atoi (substr c 1 3)))
(setq b (atof (substr c 5 3)))
(setq a (atof (substr c 9 3)))
(setq e (atof (substr c 13 5)))
(setq r e)
(setq h1 (atoi (substr c 27 3)))

;
(setq pc (getpoint "Point d'insertion :"))
(setvar "osmode" 0)
(setq pt_i pc)
(setq pt_cen (setq pt_i pc))
(setq pt_bg (polar pc (der 0) (/ h 2.0)))
(setq pt_bc (setq pt_i pc))
(setq pt_bd (polar pc (der 180) (/ h 2)))
(setq pt_cc (polar pt_bg (der 270) (/ b 2.0)))
(setq pt_hg (polar pt_bd (der 270) (/ b 2.0)))
(setq pt_hc (polar pt_bg (der 270) b))
(setq pt_hd (polar pt_bd (der 270) b))
(rech_pti)

(setq pt1 (polar pc (der 180) (/ h 2.0)))
(setq pt2 (polar pt1 (der 90) b ))
(setq pt3 (polar pt2 (der 0) e ))
(setq pt4 (polar pt3 (der 270) (- b (+ a r))))
(setq pt5 (polar pt4 (der 270) r))
(setq pt5 (polar pt5 (der 0) r))
(setq pt6 (polar pt5 (der 0) (- h (+ e e r r))))
(setq pt7 (polar pt6 (der 90) r))
(setq pt7 (polar pt7 (der 0) r))
(setq pt8 (polar pt7 (der 90) (- b (+ a r))))
(setq pt9 (polar pt8 (der 0) e))
(setq pt10 (polar pt9 (der 270) b))

;
(setvar "osmode" 0)
(command "_.pline" pt1 "_w" 0 "" pt2 pt3 pt4 "A" "r" r pt5 "LI" pt6 "A" "r" r pt7
"LI" pt8 pt9 pt10 "c")
(rot)
)


;                       *****************************************
;                       *       GENERATEUR DE UPE               *
;                       *****************************************
(defun UPE (/ plan)
(setq h (atoi (substr c 1 3)))
(setq b (atof (substr c 5 3)))
(setq a (atof (substr c 9 4)))
(setq e (atof (substr c 14 5)))
(setq r (atof (substr c 20 4)))
(setq h1 (atoi (substr c 25 3)))

;
(setq pc (getpoint "Point d'insertion :"))
(setvar "osmode" 0)
(setq pt_i pc)
(setq pt_cen (setq pt_i pc))
(setq pt_bg (polar pc (der 0) (/ h 2.0)))
(setq pt_bc (setq pt_i pc))
(setq pt_bd (polar pc (der 180) (/ h 2.0)))
(setq pt_cc (polar pt_bg (der 270) (/ b 2.0)))
(setq pt_hg (polar pt_bd (der 270) (/ b 2.0)))
(setq pt_hc (polar pt_bg (der 270) b))
(setq pt_hd (polar pt_bd (der 270) b))
(rech_pti)

(setq pt1 (polar pc (der 180) (/ h 2.0)))
(setq pt2 (polar pt1 (der 90) b ))
(setq pt3 (polar pt2 (der 0) e ))
(setq pt4 (polar pt3 (der 270) (- b (+ a r))))
(setq pt5 (polar pt4 (der 270) r))
(setq pt5 (polar pt5 (der 0) r))
(setq pt6 (polar pt5 (der 0) (- h (+ e e r r))))
(setq pt7 (polar pt6 (der 90) r))
(setq pt7 (polar pt7 (der 0) r))
(setq pt8 (polar pt7 (der 90) (- b (+ a r))))
(setq pt9 (polar pt8 (der 0) e))
(setq pt10 (polar pt9 (der 270) b))

;
(setvar "osmode" 0)
(command "_.pline" pt1 "_w" 0 "" pt2 pt3 pt4 "A" "r" r pt5 "LI" pt6 "A" "r" r pt7
"LI" pt8 pt9 pt10 "c")
(rot)
)

;                       *****************************************
;                       *       GENERATEUR DE UPN               *
;                       *****************************************

(defun upn ()
(setq h (atoi (substr c 1 3)))
(setq b (atof (substr c 5 3)))
(setq a (atof (substr c 9 4)))
(setq e (atof (substr c 14 4)))
(setq r (atof (substr c 19 4)))
(setq r1 (atof (substr c 24 3)))
(setq h1 (atof (substr c 28 3)))
;
(setq alpha 0.07982998571)
(setq beta (- (/ pi 2) alpha))
(setq x1 (* r (sin beta)))
(setq y1 (- r (* r (cos beta))))
(setq x2 (* r1 (sin beta)))
(setq y2 (- r1 (* r1 (cos beta))))
(setq 1x(/ h 2))
(setq xx(- 1x e))
(setq yy(/ b 2))
(setq u(- (/ b 2) y2))
(setq v(* u 0.08))
;
(setq pc (getpoint "Point d'insertion :"))
(setvar "osmode" 0)
(setq pt_cen (setq pt_i pc))
(setq pt_bg (polar pc (der 0) (/ h 2.0)))
(setq pt_bc (setq pt_i pc))
(setq pt_bd (polar pc (der 180) (/ h 2.0)))
(setq pt_cc (polar pt_bg (der 270) (/ b 2)))
(setq pt_hg (polar pt_bd (der 270) (/ b 2)))
(setq pt_hc (polar pt_bg (der 270) b))
(setq pt_hd (polar pt_bd (der 270) b))
(rech_pti)
(setq pt1 (polar pc (der 180) 1x))
(setq pt2 (polar pt1 (der 90) b))
(setq pt6 (polar pc (der 180) (/ h1 2.0)))
(setq pt6 (polar pt6 (der 90) a))
(setq pt5 (polar pt6 (der 180) x1))
(setq pt5 (polar pt5 (der 90) y1))
(setq p1 (polar pc (der 180) (- 1x e)))
(setq p1 (polar p1 (der 90) (/ b 2)))
(setq pt4 (polar p1 (der 180) v))
(setq pt4 (polar pt4 (der 90) u))
(setq pt3 (polar pt4 (der 180) x2))
(setq pt3 (polar pt3 (der 90) y2))
(setq po1 (polar pt3 (der 0) r1))

(setq pt12 (polar pc (der 0) 1x))
(setq pt11 (polar pt12 (der 90) b))
(setq pt7 (polar pc (der 0) (/ h1 2.0)))
(setq pt7 (polar pt7 (der 90) a))
(setq pt8 (polar pt7 (der 0) x1))
(setq pt8 (polar pt8 (der 90) y1))
(setq p2 (polar pc (der 0) (- 1x e)))
(setq p2 (polar p2 (der 90) (/ b 2.0)))
(setq pt9 (polar p2 (der 0) v))
(setq pt9 (polar pt9 (der 90) u))
(setq pt10 (polar pt9 (der 0) x2))
(setq pt10 (polar pt10 (der 90) y2))
(setq po2 (polar pt10 (der 180) r1))

;
(setvar "osmode" 0)
(command "_.pline" pt1 "_w" 0 "" "_w" 0 "" pt2 pt3 "a" "DI" po1 pt4 "LI" p1 pt5 "A" "R" r pt6 "LI" pt7
"A" "R" r pt8 "LI" p2 pt9 "a" "DI" po2 pt10 "LI" pt11 pt12 "c")
(rot)
)
;**********************************************************************

;                       *****************************************
;                       *    SOUS PROGRAMME DE ROTATION         *
;                       *****************************************
(defun rot ()
	(setvar "osmode" ini_obj)
	(if (= rotation "pause") (command "_rotate" "_l" "" pt_i pause)
	(command "_rotate" "_l" "" pt_i rotation)
	)
	(setvar "orthomode" ini_ortho)
	(if (= bloc_action 1) (aplic_bloc))
(command "_.redraw")
)

;**********************************************************************
;**********mise a 0 des cases
(defun mise_zero ()
        (setq rot1 0)
        (setq rot2 0)
        (setq rot3 0)
        (setq rot4 0)
        (setq rot5 0)
        (setq rot6 0)
        (setq rot7 0)

	(set_tile ;|MSG0|;"rot1" ;|MSG0|;"0")
	(set_tile ;|MSG0|;"rot2" ;|MSG0|;"0")
	(set_tile ;|MSG0|;"rot3" ;|MSG0|;"0")
	(set_tile ;|MSG0|;"rot4" ;|MSG0|;"0")
	(set_tile ;|MSG0|;"rot5" ;|MSG0|;"0")
	(set_tile ;|MSG0|;"rot6" ;|MSG0|;"0")
	(set_tile ;|MSG0|;"rot7" ;|MSG0|;"0")


)
;**********selection**
(defun selec_1 ()
	(mise_zero)
	(set_tile ;|MSG0|;"rot1" ;|MSG0|;"1")
	(setq rotation "0"))
(defun selec_2 ()
	(mise_zero)
	(set_tile ;|MSG0|;"rot2" ;|MSG0|;"1")
	(setq rotation "45"))
(defun selec_3 ()
	(mise_zero)
	(set_tile ;|MSG0|;"rot3" ;|MSG0|;"1")
	(setq rotation "90"))
(defun selec_4 ()
	(mise_zero)
	(set_tile ;|MSG0|;"rot4" ;|MSG0|;"1")
	(setq rotation "pause"))
(defun selec_5 ()
	(mise_zero)
	(set_tile ;|MSG0|;"rot5" ;|MSG0|;"1")
	(setq rotation "180"))
(defun selec_6 ()
	(mise_zero)
	(set_tile ;|MSG0|;"rot6" ;|MSG0|;"1")
	(setq rotation "-45"))
(defun selec_7 ()
	(mise_zero)
	(set_tile ;|MSG0|;"rot7" ;|MSG0|;"1")
	(setq rotation "-90"))


(defun CBLOC ()
  (if (= "?" type_fer)
      (progn
	(alert "AUCUNE SELECTION N'A ETE FAITE")
	(set_tile ;|MSG0|;"cbloc" ;|MSG0|;"0")
	)
      (progn
	(setq nom_bl (strcat fer type_fer))
	(nombbloc)
	(if (= bloc_action 0)
		(progn
		(setq bloc_action 1)
		(setq filtre nom_bl)
		(comparatif)
		(set_tile ;|MSG0|;"cbloc" ;|MSG0|;"1")
		(set_tile "nomdubloc" ;|MSG0|; nom_bl)
		(setq oui nil)
		)
		(progn
		(set_tile "nomdubloc" ;|MSG0|; "aucun")
		(setq bloc_action 0)
		)
	)
      )
  )
)
(defun def_BLOC (/ value)
(if (= "?" type_fer)
      (progn
	(alert "AUCUNE SELECTION N'A ETE FAITE")
	(set_tile ;|MSG0|;"cbloc" ;|MSG0|;"0")
	)
      (progn
	(setq oui nil)
	(setq nom_bl (strcat fer type_fer))
	(nombbloc)
	(def_BLOC2)
	(setq filtre (strcat fer "*"))
	(rech_bloc)
	(set_tile ;|MSG0|;"filtre_b" filtre)
(set_tile "nomdubloc" ;|MSG0|; nom_bl)
      )
)
)

(defun def_BLOC2 (/ value)
	(setq bloc_action 1)
	(set_tile ;|MSG0|;"cbloc" ;|MSG0|;"1")
	(new_dialog "list_bloc" sc_dcl_id)
	(rech_bloc)
	(set_tile "nom_bl" ;|MSG0|;nom_bl)
	(action_tile ;|MSG0|;"filtre_b" ;|MSG0|;"(new_filtre $value)")
	(action_tile ;|MSG0|;"nom_bl" ;|MSG0|;"(nom_blo $value)")
	(action_tile "list_bloc" "(new_bloc $value)")
	(start_dialog)
)

(defun new_filtre (value)
(setq filtre (xstrcase $value))
(rech_bloc)
)
(defun nom_blo ()
	(setq nom_bl (xstrcase $value))
	(setq filtre nom_bl)
	(rech_bloc)
	(if (/= nb_bloc 0) (alerte))
)
(defun alerte ()
	(setq oui nil)
	(new_dialog "redefinir" sc_dcl_id)
	(action_tile "yes" "(setq oui 1)(done_dialog 2)")
;	(action_tile "no" "(nombbloc)(done_dialog 2)")
	(start_dialog)

)

(defun nombbloc ()
(setq nom_bl2 nom_bl)
(setq nbre2 0)
(setq filtre nom_bl)
(comparatif)
   (while (/= nb_bloc 0)
	(setq nbre2 (+ nbre2 1))
	(setq nbre (itoa nbre2))
	(setq nom_bl (strcat nom_bl2  "_" nbre))
	(setq filtre nom_bl)
	(comparatif)
	(setq filtre (strcat fer type_fer "*"))
   )
)
(defun new_bloc (value)
	(setq nomblocinit nom_bl)
	(setq sel value)
	(setq rech 0)
	(while (/= rech (atoi sel))
		(setq selec_list_bl (cdr selec_list_bl))
		(setq rech (+ rech 1))
	)
	(setq selec_list_bl (car selec_list_bl))
	(if (/= nil selec_list_bl)
	(progn
	(set_tile "nom_bl" ;|MSG0|;selec_list_bl)
	(setq nom_bl selec_list_bl)
	(alerte)
	)
)
)

;****************aplic bloc
(defun aplic_bloc ()
	(setvar "osmode" 0)
	(if (not oui)
	(command "_block" nom_bl pt_i "_last" "")
	(command "_block" nom_bl "_y" pt_i "_last" "")
	)
	(command "_insert" nom_bl pt_i 1 1 0 ) 
	(setvar "osmode" ini_obj)
)
;*******recherche bloc***
(defun rech_bloc ()
	(setq liste_bloc '())
	(setq filtre (strcase filtre))
	(set_tile ;|MSG0|;"filtre_b" filtre)
	(comparatif)
	(start_list "list_bloc")
	(mapcar 'add_list liste_bloc)
	(end_list)
	(setq selec_list_bl liste_bloc)
;	(set_tile ;|MSG0|;"filtre_b" filtre)

)
(defun comparatif ()
(setq liste_bloc '())

	(setq enti_bloc (tblnext "block" t))
	(while (/= enti_bloc nil)
		(setq nom_bloc (cdr (assoc 2 enti_bloc)))
		(setq teste (wcmatch nom_bloc filtre))
		(if (= teste t)
			(setq liste_bloc (cons nom_bloc liste_bloc))
		)
		(setq enti_bloc (tblnext "block"))		
	)
	(setq nb_bloc (length liste_bloc))
)
;*********************image point d'incertion
(defun ip_image ()
	(setq imag "imag1")
	(setq clicher "ie_cg")
	(image)
	(setq imag "imag2")
	(setq clicher "ie_bg")
	(image)
	(setq imag "imag3")
	(setq clicher "ie_bc")
	(image)
	(setq imag "imag4")
	(setq clicher "ie_bd")
	(image)
	(setq imag "imag5")
	(setq clicher "ie_gg")
	(image)
	(setq imag "imag6")
	(setq clicher "ie_hg")
	(image)
	(setq imag "imag7")
	(setq clicher "ie_hc")
	(image)
	(setq imag "imag8")
	(setq clicher "ie_hd")
	(image)
)
(defun h_image ()
	(setq imag "imag1")
	(setq clicher "ha_cg")
	(image)
	(setq imag "imag2")
	(setq clicher "ha_bg")
	(image)
	(setq imag "imag3")
	(setq clicher "ha_bc")
	(image)
	(setq imag "imag4")
	(setq clicher "ha_bd")
	(image)
	(setq imag "imag5")
	(setq clicher "ha_gg")
	(image)
	(setq imag "imag6")
	(setq clicher "ha_hg")
	(image)
	(setq imag "imag7")
	(setq clicher "ha_hc")
	(image)
	(setq imag "imag8")
	(setq clicher "ha_hd")
	(image)
)
(defun u_image ()
	(setq imag "imag1")
	(setq clicher "un_cg")
	(image)
	(setq imag "imag2")
	(setq clicher "un_bg")
	(image)
	(setq imag "imag3")
	(setq clicher "un_bc")
	(image)
	(setq imag "imag4")
	(setq clicher "un_bd")
	(image)
	(setq imag "imag5")
	(setq clicher "un_gg")
	(image)
	(setq imag "imag6")
	(setq clicher "un_gd")
	(image)
	(setq imag "imag7")
	(setq clicher "un_hg")
	(image)
	(setq imag "imag8")
	(setq clicher "un_hd")
	(image)
)
(defun c_image ()
	(setq imag "imag1")
	(setq clicher "l_cg")
	(image)
	(setq imag "imag2")
	(setq clicher "l_bg")
	(image)
	(setq imag "imag3")
	(setq clicher "l_bc")
	(image)
	(setq imag "imag4")
	(setq clicher "l_bd")
	(image)
	(setq imag "imag5")
	(setq clicher "l_gg")
	(image)
	(setq imag "imag6")
	(setq clicher "l_gb")
	(image)
	(setq imag "imag7")
	(setq clicher "l_hg")
	(image)
	(setq imag "imag8")
	(setq clicher "l_gc")
	(image)
)

;*************image 
(defun point_inser ()
	(setq selec_cancel selec_imag)
	(setq list_imag '())
	(if (not (new_dialog "insert" sc_dcl_id)) (exit))
	(if (= image_fer "ip") (ip_image))
	(if (= image_fer "h") (h_image))
	(if (= image_fer "u") (u_image))
	(if (= image_fer "c") (c_image))
	(action_tile "imag1" "(setq selec_imag 8)")
	(action_tile "imag2" "(setq selec_imag 7)")
	(action_tile "imag3" "(setq selec_imag 6)")
	(action_tile "imag4" "(setq selec_imag 5)")
	(action_tile "imag5" "(setq selec_imag 4)")
	(action_tile "imag6" "(setq selec_imag 3)")
	(action_tile "imag7" "(setq selec_imag 2)")
	(action_tile "imag8" "(setq selec_imag 1)")
	(action_tile "cancel" "(setq selec_imag selec_cancel)")
	(start_dialog)
(setq nb_imag 1)
(while (/= nb_imag selec_imag)
	(setq list_imag (cdr list_imag))
	(setq nb_imag (+ nb_imag 1))
	(if (= nb_imag 10) (setq nb_imag selec_imag))
)
(setq imag "m_imag")
(setq clicher (car list_imag))
(image)
)   

(defun image ()
	(setq list_imag (cons clicher list_imag))
(setq x (dimx_tile imag)
      y (dimy_tile imag))
(start_image imag)
(fill_image 0 0 x y 0)

(slide_image 0 0 x y (strcat (strcat racine_dossier "/dcl/gene_pro.slb (") clicher ")"))

(end_image)
)
(defun menu_image ()
	(setq imag "m_imag")
	(setq selec_imag 8)
	(if (= image_fer "ip") (setq clicher "ie_cg"))
	(if (= image_fer "h") (setq clicher "ha_cg"))
	(if (= image_fer "u") (setq clicher "un_cg"))
	(if (= image_fer "c") (setq clicher "l_cg"))
	(image)
)

(defun rech_pti ()
	(if (= selec_imag 8) (setq pc pt_cen))	
	(if (= selec_imag 7) (setq pc pt_bg))	
	(if (= selec_imag 6) (setq pc pt_bc)) 	
	(if (= selec_imag 5) (setq pc pt_bd))	
	(if (= selec_imag 4) (setq pc pt_cc))	
	(if (= selec_imag 3) (setq pc pt_hg))	
	(if (= selec_imag 2) (setq pc pt_hc)) 	
	(if (= selec_imag 1) (setq pc pt_hd))	
)
;;;;;;;;;;;;;;;;;;;;;;;;;;;;;;;;;;;;;;;;;;;;;;;;;;;;;;;;
;******Chargement info**********
(defun info ()
(setq info1 (open (strcat racine_dossier "/lisp/profil.lsp" "r")))
(setq nbr 0)
(setq list_info '())
	(while (/= nbr 3)
	 (setq info2 (read-line info1))
 	 (setq nbr (+ nbr 1))
	 (setq list_info (cons info2 list_info))
	)
(close info1)
(setq i1 (caddr list_info))
(setq i2 (cadr list_info))
(setq i3 (car list_info))
(setq info3 (strcat "\n" i1 "\r" i2 "\r" i3 ))
(alert info3)
)

(princ)
(prompt "\nN.D.I. - Générateur de profil.")
