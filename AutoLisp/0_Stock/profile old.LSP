(defun c:pf ()
  (setq	cmde (getvar "CMDECHO")
	hp   (getvar "HPBOUND")
	snap (getvar "AUTOSNAP")
  ) ;_ Fin de setq
  (setvar "CMDECHO" 0)
  (setvar "HPBOUND" 0)
  (setvar "AUTOSNAP" 2)
  (setq view (car(entsel "\nSelectionnez la fenêtre à modifier"))
	point (getpoint "\nIndiquez un point à l'interieur de la nouvelle fenêtre à créer :")
	point (list (car point) (cadr point))
	)
  (princ point)
  (command "_.-boundary" point "")
  (command "_VPCLIP" view (entlast))
  (setvar "CMDECHO" cmde)
  (setvar "HPBOUND" hp)
  (setvar "AUTOSNAP" snap)
  (princ)
) ;_ Fin de defun
