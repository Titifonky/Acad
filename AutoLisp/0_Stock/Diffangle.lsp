(defun c:dif ()
  (setq	pt1 (getpoint "\nPoint1")
	pt2 (getpoint pt1 "\nPoint2")
	pt3 (getpoint "\nPoint3")
	pt4 (getpoint pt3 "\nPoint4")
  )
  (setq	x1 (float (- (car pt2) (car pt1)))
	y1 (float (- (cadr pt2) (cadr pt1)))
	x2 (float (- (car pt4) (car pt3)))
	y2 (float (- (cadr pt4) (cadr pt3)))
  )
  (if (zerop x1)
    (setq angle1 (* (/ pi 2) (/ y1 (abs y1))))
    (if	(zerop y1)
      (setq angle1 0)
      (setq angle1 (atan (/ y1 x1)))
    )
  )
  (if (zerop x2)
    (setq angle2 (* (/ pi 2) (/ y2 (abs y2))))
    (if	(zerop y2)
      (setq angle2 0)
      (setq angle2 (atan (/ y2 x2)))
    )
  )
  (princ "\n")
  (setq angl (- angle2 angle1))
  (princ angl)
  (princ)
)

(defun c:diff ()
  (setq	pt1 (getpoint "\nPoint1")
	pt2 (getpoint pt1 "\nPoint2")
	pt3 (getpoint "\nPoint3")
	pt4 (getpoint pt3 "\nPoint4")
  )
  (setq angle1 (angle pt1 pt2))
  (setq angle2 (angle pt3 pt4))
  (setq angldiff (atof (angtos (- angle2 angle1) 3 6)))
  (if (> angldiff pi)
    (setq angldiff (- angldiff (* pi 2)))
  )
  (princ "\n")
  (princ angldiff)
  (princ)
)
