(defun div (listent / )
(setq listent (vl-remove-if-not '(lambda (x) (or (= 0 (car x)) 
(= 10 (car x))
(= 11 (car x))
(and (not (= 0.0 (cdr x))) (= 41 (car x)))
(and (not (= 0.0 (cdr x))) (= 42 (car x)))
(= 50 (car x))
(= 51 (car x))
(= 70 (car x)))
)
listent))
)

(defun c:diva ()
(setq nomobj (car (entsel "\nSelectionnez l'objet à couper :")))
(setq listent (entget nomobj))
(setq entdata (div listent))
(princ "\nSelectionnez les objets coupants :")
(setq objsel (ssget))
(if (ssmemb nomobj objsel)
(setq objsel (ssdel nomobj objsel))
)
(setq listent (entget (ssname objsel 0)))
(setq entitesdata (div listent))
(setq i 1)
(while (ssname objsel i)
(setq listent (entget (ssname objsel i)))
(setq entitesdata (append entitesdata (div listent)))
(setq i (1+ i))
)
