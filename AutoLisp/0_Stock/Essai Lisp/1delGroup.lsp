(defun c:dg(/ i namesel entdef)
(if (setq namesel (ssget))
(progn
(setq i 0)
(while (ssname namesel i)
(setq entdef (entget (ssname namesel i)))
(if (= (cdr (assoc 102 entdef)) "{ACAD_REACTORS")
(entdel (cdr (assoc 330 entdef)))
)
(setq i (1+ i))
)
)
)
(princ)
)
